FME workspace convert_mm_to_gdb_working_bat.fmw

Parameters:
- DestDataset_GDB = M:/downloaded/20170726   # Destination Geodatabase
- SourceDataset_GML = M:\downloaded20170726\OS_MasterMap_Topography___5km_2651348_TL0000.gz   # Source OS (GB) MasterMap File(s)
- DestDataset_FILEGDB = C:\temp\osmm_20170804.gdb   # File Geodatabase
- tester = tester

Readers:
- DNF_1: DNF from $(SourceDataset_GML)

Writers:
- FILEGDB_1: FILEGDB to $(DestDataset_FILEGDB)

Note: modify readers and writers so they look for paramaters or are dynamic so properties do not need to be changed every time

Bookmark: Convert OS MasterMap
CartographicSymbol (reader DNF_1)
    attributes: xml_rotation xml_real64, TOID xml_char(16), FeatureCode xml_int16, Version xml_int16, VersionDate xml_char(10), Theme xml_char(64), ThemeCount xml_int16, ChangeDate xml_char(10), ReasonForChange xml_char(36), ChangeHistory{}.ChangeDate xml_char(10), ChangeHistory{}.ReasonForChange xml_char(36), ChangeHistoryCount xml_int16, DescriptiveGroup xml_char(254), DescriptiveGroupCount xml_int16, DescriptiveTerm xml_char(254), DescriptiveTermCount xml_int16, Orientation xml_int16, PhysicalLevel xml_int16, PhysicalPresence xml_char(16), ReferenceToFeature{} xml_char(16)
    -> AttributeExposer_4
AttributeExposer_4
    ATTR_LIST = fme_basename
    -> AttributeRenamer_2
AttributeRenamer_2
    ATTR_TABLE = RENAME_SET_DEFAULT fme_basename > tile
    -> AttributeCreator_5
AttributeCreator_5
    ATTR_TABLE = SET_TO file = $(SourceDataset_GML)
    -> CartographicSymbol (writer FILEGDB_1)
CartographicSymbol (writer FILEGDB_1)
    attributes: xml_rotation double, TOID text(16), FeatureCode smallint, Version smallint, VersionDate text(10), Theme text(64), ThemeCount smallint, ChangeDate text(10), ReasonForChange text(36), ChangeHistoryCount text(20), DescriptiveGroup text(254), DescriptiveGroupCount smallint, DescriptiveTerm text(254), DescriptiveTermCount smallint, Orientation smallint, PhysicalLevel smallint, PhysicalPresence text(16)
TopographicArea (reader DNF_1)
    attributes: TOID xml_char(16), FeatureCode xml_int16, Version xml_int16, VersionDate xml_char(10), Theme xml_char(64), ThemeCount xml_int16, CalculatedAreaValue xml_real64, ChangeDate xml_char(10), ReasonForChange xml_char(36), ChangeHistory{}.ChangeDate xml_char(10), ChangeHistory{}.ReasonForChange xml_char(36), ChangeHistoryCount xml_int16, DescriptiveGroup xml_char(254), DescriptiveGroupCount xml_int16, DescriptiveTerm xml_char(254), DescriptiveTermCount xml_int16, Make xml_char(12), PhysicalLevel xml_int16, PhysicalPresence xml_char(16), broken xml_char(5)
    -> AttributeExposer
AttributeExposer
    ATTR_LIST = fme_feature_type,fme_basename
    -> AttributeRenamer
Note: fme_basename to 'tile'
AttributeRenamer
    ATTR_TABLE = RENAME_SET_DEFAULT fme_basename > tile
    -> AttributeCreator
AttributeCreator
    ATTR_TABLE = SET_TO file = $(SourceDataset_GML)
    -> TopographicArea (writer FILEGDB_1)
TopographicArea (writer FILEGDB_1)
    attributes: TOID text(16), FeatureCode smallint, Version smallint, VersionDate text(10), Theme text(64), ThemeCount smallint, CalculatedAreaValue double, ChangeDate text(10), ReasonForChange text(36), ChangeHistoryCount text(20), DescriptiveGroup text(254), DescriptiveGroupCount smallint, DescriptiveTerm text(254), DescriptiveTermCount smallint, Make text(12), PhysicalLevel smallint, PhysicalPresence text(16), broken text(5)
TopographicLine (reader DNF_1)
    attributes: TOID xml_char(16), FeatureCode xml_int16, Version xml_int16, VersionDate xml_char(10), Theme xml_char(64), ThemeCount xml_int16, AccuracyOfPosition xml_char(7), ChangeDate xml_char(10), ReasonForChange xml_char(36), ChangeHistory{}.ChangeDate xml_char(10), ChangeHistory{}.ReasonForChange xml_char(36), ChangeHistoryCount xml_int16, DescriptiveGroup xml_char(254), DescriptiveGroupCount xml_int16, DescriptiveTerm xml_char(254), DescriptiveTermCount xml_int16, NonBoundingLine xml_boolean, HeightAboveDatum xml_real64, AccuracyOfHeightAboveDatum xml_char(7), HeightAboveGroundLevel xml_real64, AccuracyOfHeightAboveGroundLevel xml_char(7), Make xml_char(12), PhysicalLevel xml_int16, PhysicalPresence xml_char(16), ReferenceToFeature xml_char(16), broken xml_char(5)
    -> AttributeExposer_2
AttributeExposer_2
    ATTR_LIST = fme_basename
    -> AttributeRenamer_9
AttributeRenamer_9
    ATTR_TABLE = RENAME_SET_DEFAULT fme_basename > tile
    -> AttributeCreator_2
AttributeCreator_2
    ATTR_TABLE = SET_TO file = $(SourceDataset_GML)
    -> TopographicLine (writer FILEGDB_1)
TopographicLine (writer FILEGDB_1)
    attributes: TOID text(16), FeatureCode smallint, Version smallint, VersionDate text(10), Theme text(64), ThemeCount smallint, AccuracyOfPosition text(7), ChangeDate text(10), ReasonForChange text(36), ChangeHistoryCount text(20), DescriptiveGroup text(254), DescriptiveGroupCount smallint, DescriptiveTerm text(254), DescriptiveTermCount smallint, NonBoundingLine smallint, HeightAboveDatum double, AccuracyOfHeightAboveDatum text(7), HeightAboveGroundLevel double, AccuracyOfHeightAboveGroundLevel text(7), Make text(12), PhysicalLevel smallint, PhysicalPresence text(16), ReferenceToFeature text(16), broken text(5)
BoundaryLine (reader DNF_1)
    attributes: TOID xml_char(16), FeatureCode xml_int16, Version xml_int16, VersionDate xml_char(10), Theme xml_char(64), ThemeCount xml_int16, AccuracyOfPosition xml_char(7), ChangeDate xml_char(10), ReasonForChange xml_char(36), ChangeHistory{}.ChangeDate xml_char(10), ChangeHistory{}.ReasonForChange xml_char(36), ChangeHistoryCount xml_int16, DescriptiveGroup xml_char(254), DescriptiveGroupCount xml_int16, DescriptiveTerm xml_char(254), DescriptiveTermCount xml_int16, Make xml_char(12), PhysicalLevel xml_int16, PhysicalPresence xml_char(16), broken xml_char(5)
    -> AttributeExposer_3
AttributeExposer_3
    ATTR_LIST = fme_basename
    -> AttributeRenamer_8
AttributeRenamer_8
    ATTR_TABLE = RENAME_SET_DEFAULT fme_basename > tile
    -> AttributeCreator_3
AttributeCreator_3
    ATTR_TABLE = SET_TO file = $(SourceDataset_GML)
    -> BoundaryLine (writer FILEGDB_1)
BoundaryLine (writer FILEGDB_1)
    attributes: TOID text(16), FeatureCode smallint, Version smallint, VersionDate text(10), Theme text(64), ThemeCount smallint, AccuracyOfPosition text(7), ChangeDate text(10), ReasonForChange text(36), ChangeHistoryCount text(20), DescriptiveGroup text(254), DescriptiveGroupCount smallint, DescriptiveTerm text(254), DescriptiveTermCount smallint, Make text(12), PhysicalLevel smallint, PhysicalPresence text(16), broken text(5)
TopographicPoint (reader DNF_1)
    attributes: TOID xml_char(16), FeatureCode xml_int16, Version xml_int16, VersionDate xml_char(10), Theme xml_char(64), ThemeCount xml_int16, AccuracyOfPosition xml_char(7), ChangeDate xml_char(10), ReasonForChange xml_char(36), ChangeHistory{}.ChangeDate xml_char(10), ChangeHistory{}.ReasonForChange xml_char(36), ChangeHistoryCount xml_int16, DescriptiveGroup xml_char(254), DescriptiveGroupCount xml_int16, DescriptiveTerm xml_char(254), DescriptiveTermCount xml_int16, HeightAboveDatum xml_real64, AccuracyOfHeightAboveDatum xml_char(7), HeightAboveGroundLevel xml_real64, AccuracyOfHeightAboveGroundLevel xml_char(7), Make xml_char(12), PhysicalLevel xml_int16, PhysicalPresence xml_char(16), ReferenceToFeature xml_char(16)
    -> AttributeExposer_7
AttributeExposer_7
    ATTR_LIST = fme_basename
    -> AttributeRenamer_7
AttributeRenamer_7
    ATTR_TABLE = RENAME_SET_DEFAULT fme_basename > tile
    -> AttributeCreator_4
AttributeCreator_4
    ATTR_TABLE = SET_TO file = $(SourceDataset_GML)
    -> TopographicPoint (writer FILEGDB_1)
TopographicPoint (writer FILEGDB_1)
    attributes: TOID text(16), FeatureCode smallint, Version smallint, VersionDate text(10), Theme text(64), ThemeCount smallint, AccuracyOfPosition text(7), ChangeDate text(10), ReasonForChange text(36), ChangeHistoryCount text(20), DescriptiveGroup text(254), DescriptiveGroupCount smallint, DescriptiveTerm text(254), DescriptiveTermCount smallint, HeightAboveDatum double, AccuracyOfHeightAboveDatum text(7), HeightAboveGroundLevel double, AccuracyOfHeightAboveGroundLevel text(7), Make text(12), PhysicalLevel smallint, PhysicalPresence text(16), ReferenceToFeature text(16)
CartographicText (reader DNF_1)
    attributes: TOID xml_char(16), FeatureCode xml_int16, Version xml_int16, VersionDate xml_char(10), Theme xml_char(64), ThemeCount xml_int16, ChangeDate xml_char(10), ReasonForChange xml_char(36), ChangeHistory{}.ChangeDate xml_char(10), ChangeHistory{}.ReasonForChange xml_char(36), ChangeHistoryCount xml_int16, DescriptiveGroup xml_char(254), DescriptiveGroupCount xml_int16, DescriptiveTerm xml_char(254), DescriptiveTermCount xml_int16, Make xml_char(12), PhysicalLevel xml_int16, PhysicalPresence xml_char(16), AnchorPosition xml_decimal(3,0), Font xml_decimal(3,0), Height xml_real32, Orientation xml_int16, TextString xml_char(254)
    -> AttributeExposer_5
AttributeExposer_5
    ATTR_LIST = fme_basename
    -> AttributeRenamer_6
AttributeRenamer_6
    ATTR_TABLE = RENAME_SET_DEFAULT fme_basename > tile
    -> AttributeCreator_6
AttributeCreator_6
    ATTR_TABLE = SET_TO file = $(SourceDataset_GML)
    -> CartographicText (writer FILEGDB_1)
CartographicText (writer FILEGDB_1)
    attributes: TOID text(16), FeatureCode smallint, Version smallint, VersionDate text(10), Theme text(64), ThemeCount smallint, ChangeDate text(10), ReasonForChange text(36), ChangeHistoryCount text(20), DescriptiveGroup text(254), DescriptiveGroupCount smallint, DescriptiveTerm text(254), DescriptiveTermCount smallint, Make text(12), PhysicalLevel smallint, PhysicalPresence text(16), AnchorPosition double, Font double, Height single, Orientation smallint, TextString text(254)
queryExtent (reader DNF_1)
    -> AttributeExposer_6
AttributeExposer_6
    ATTR_LIST = fme_feature_type,fme_basename
    -> AttributeRenamer_5
AttributeRenamer_5
    ATTR_TABLE = RENAME_SET_DEFAULT fme_basename > tile
    -> AttributeCreator_7
AttributeCreator_7
    ATTR_TABLE = SET_TO file = $(SourceDataset_GML)
    -> queryExtent (writer FILEGDB_1)
queryExtent (writer FILEGDB_1)
