FME workspace geodatabase_file2filegdb.fmw

Parameters:
- DestDataset_GEODATABASE_FILE = C:\temp\osmm_20170804.gdb   # Destination Esri File Geodatabase
- SourceDataset_GEODATABASE_FILE = C:\temp\osmm_20170804.gdb   # File Geodatabase

Readers:
- GEODATABASE_FILE_1: GEODATABASE_FILE from $(SourceDataset_GEODATABASE_FILE)

Writers:
- GEODATABASE_FILE_2: GEODATABASE_FILE to $(DestDataset_GEODATABASE_FILE) in BritishNatGrid

TopographicArea (reader GEODATABASE_FILE_1)
    attributes: TOID char(16), FeatureCode smallint, Version smallint, VersionDate char(10), Theme char(64), ThemeCount smallint, CalculatedAreaValue double, ChangeDate char(10), ReasonForChange char(36), ChangeHistoryCount char(20), DescriptiveGroup char(254), DescriptiveGroupCount smallint, DescriptiveTerm char(254), DescriptiveTermCount smallint, Make char(12), PhysicalLevel smallint, PhysicalPresence char(16), broken char(5), OBJECTID integer
    -> Tester
Tester
    TEST_MODE = Automatic
    BOOL_OP = OR
    TEST_DESCRIPTION = ""
    TEST_CLAUSE = TEST @Value(Theme) = Buildings
    PASSED -> StringConcatenator
StringConcatenator
    VAL_ATTR = TOID2
    PARM_LINE = osgb@Value(TOID)
    -> Joiner
Note: Join to building height attribute csv file using TOID
Joiner
    CSV__DUPLICATE_DELIMS = no
    CSV__IN_SEPARATOR = ,
    DATASET = Q:\Teams\GIS&I\GIS\Processing\OrdnanceSurvey\OS MasterMap Topography Layer\BuildingHeights_Alpha_2014\Data\BHA_DEC14_England.csv
    CSV__STRIP_QUOTES = yes
    CSV__SKIP_LINES = 1
    CSV__SORT_TABLE_CONFIG = "NOT_OK_IF_INVALID%NO_LABEL%ROW_DELIM:;%COL_DELIM:,%HAS_DEFAULTS%START_NUM_ROWS:3%\"Attribute\"%\"STRING_OR_CHOICE_ENCODED ATTRIBUTES OS_TOPO_TOID%OS_TOPO_VERSION%BHA_ProcessDate%TileRef%AbsHMin%AbsH2%AbsHMax%RelH2%RelHMax%BHA_Conf\"%%\"Alpha/Num\"%\"LOOKUP_CHOICE SORT_CHOICE Alphabetic,alphabetic%Numeric,numeric\"%alphabetic%\"Order\"%\"LOOKUP_CHOICE SORT_ORDER Ascending,ascending%Descending,descending\"%ascending"
    CSV__ALLOW_SPACES_IN_COLUMN_NAMES = yes
    CSV__SCHEMA_WITH_COL_NAMES = OS_TOPO_TOID,char,17,,OS_TOPO_VERSION,number,4,0,BHA_ProcessDate,char,11,,TileRef,char,7,,AbsHMin,number,5,1,AbsH2,number,5,1,AbsHMax,number,5,1,RelH2,number,4,1,RelHMax,number,4,1,BHA_Conf,number,3,0
    CSV__SKIP_FOOTER = 0
    CSV__IN_FIELD_NAMES = YES
    CSV__GROUP_BY_DATASET = no
    CSV__SCHEMA = char,17,,number,4,0,char,11,,char,7,,number,5,1,number,5,1,number,5,1,number,4,1,number,4,1,number,3,0
    CSV__FIELD_NAMES_AFTER_HEADER = no
    ADDED_FIELDS = OS_TOPO_TOID OS_TOPO_VERSION BHA_ProcessDate TileRef AbsHMin AbsH2 AbsHMax RelH2 RelHMax BHA_Conf
    CSV__FILTER_TABLE_CONFIG = "NOT_OK_IF_INVALID%NO_LABEL%ROW_DELIM:;%COL_DELIM:,%HAS_DEFAULTS%START_NUM_ROWS:3%\"Field Name\"%\"STRING_OR_CHOICE_ENCODED ATTRIBUTES OS_TOPO_TOID%OS_TOPO_VERSION%BHA_ProcessDate%TileRef%AbsHMin%AbsH2%AbsHMax%RelH2%RelHMax%BHA_Conf\"%%\"Filter\"%\"STRING_ENCODED _FILTER_REGEX \"%%\"Invert Filter\"%\"CHECKBOX _FILTER_UNMATCHED yes%no\"%no"
    JOIN_KEYS = TOID2 OS_TOPO_TOID
    FORMAT = CSV
    CSV_SCAN_MAX_FEATURES = 10000
    TABLE = CSV
    MATCH_RULE_DISPLAY = Match First (1:0..1+)
    JOINED -> DateFormatter
Note: Format date
DateFormatter
    SRCFMT = Unknown - Automatic Detection
    INVALID_DATE_VALUE = _FME_NO_OP_
    DATE_ATTR = BHA_ProcessDate
    FMT = FME Date/Time (%Y%m%d%H%M%S)
    -> BuildingHeight (writer GEODATABASE_FILE_2)
Note: Write to gdb
BuildingHeight (writer GEODATABASE_FILE_2)
    attributes: Toid char(20), Version integer, VerDate date, FeatCode integer, Theme char(80), CalcArea double, Change char(80), DescGroup char(150), DescTerm char(150), Make char(20), PhysLevel integer, PhysPres char(20), Broken smallint, LoadDate date, OBJECTID integer, OS_TOPO_TOID integer, OS_TOPO_VERSION integer, BHA_ProcessDate date, TileRef char(200), AbsHMin double, AbsH2 double, AbsHMax double, RelH2 double, RelHMax double, BHA_Conf integer, _matched_records integer
