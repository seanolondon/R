FME workspace fgdb_postgis_AddressBasePlus_32bit.fmw

Parameters:
- DestDataset_POSTGIS = gis   # Destination PostGIS Dataset
- SourceDataset_CSV2_3 =   # Source CSV (Comma Separated Value) File(s)
- DestDataset_GEODATABASE_FILE =   # File Geodatabase

Readers:
- CSV2_1: CSV2 from $(SourceDataset_CSV2_3) in OSGB-GPS-2015

Writers:
- POSTGIS_1: POSTGIS to $(DestDataset_POSTGIS) in EPSG:27700
- GEODATABASE_FILE_1: GEODATABASE_FILE to $(DestDataset_GEODATABASE_FILE) in OSGB-GPS-2015

Note: AddressBase Plus Update Process / Author: A Gibson / Last Update: 2016-10-14

Bookmark: Update DEV 9.1 Postgres (gisapdata)
CSV (reader CSV2_1)
    attributes: V1 string, V2 string, V3 string, V4 string, V5 string, V6 string, V7 string, V8 string, V9 string, V10 string, V11 string, V12 string, V13 string, V14 string, V15 string, V16 string, V17 string, V18 string, V19 string, V20 string, V21 string, V22 string, V23 string, V24 string, V25 string, V26 string, V27 string, V28 string, V29 string, V30 string,
      V31 string, V32 string, V33 string, V34 string, V35 string, V36 string, V37 string, V38 string, V39 string, V40 string, V41 string, V42 string, V43 string, V44 string, V45 string, V46 string, V47 string, V48 string, V49 string, V50 string, V51 string, V52 string, V53 string, V54 string, V55 string, V56 string, V57 string, V58 string, V59 string, V60 string,
      V61 string, V62 string, V63 string, V64 string, V65 string, V66 string, V67 string, V68 string, V69 string, V70 string, V71 string, V72 string, V73 string, V74 string, V75 string, V76 string, V77 string
    -> AttributeRenamer
AttributeRenamer
    ATTR_TABLE:
      RENAME_SET_DEFAULT V1 > UPRN = UPRN
      RENAME_SET_DEFAULT V2 > UDPRN = UDPRN
      RENAME_SET_DEFAULT V11 > LONGITUDE = LONGITUDE
      RENAME_SET_DEFAULT V12 > RPC = RPC
      RENAME_SET_DEFAULT V13 > LOCAL_CUSTODIAN_CODE = LOCAL_CUSTODIAN_CODE
      RENAME_SET_DEFAULT V14 > COUNTRY = COUNTRY
      RENAME_SET_DEFAULT V15 > LA_START_DATE = LA_START_DATE
      RENAME_SET_DEFAULT V16 > LAST_UPDATE_DATE = LAST_UPDATE_DATE
      RENAME_SET_DEFAULT V17 > ENTRY_DATE = ENTRY_DATE
      RENAME_SET_DEFAULT V18 > RM_ORGANISATION_NAME = RM_ORGANISATION_NAME
      RENAME_SET_DEFAULT V19 > LA_ORGANISATION = LA_ORGANISATION
      RENAME_SET_DEFAULT V20 > DEPARTMENT_NAME = DEPARTMENT_NAME
      RENAME_SET_DEFAULT V3 > CHANGE_TYPE = CHANGE_TYPE
      RENAME_SET_DEFAULT V21 > LEGAL_NAME = LEGAL_NAME
      RENAME_SET_DEFAULT V22 > SUB_BUILDING_NAME = SUB_BUILDING_NAME
      RENAME_SET_DEFAULT V23 > BUILDING_NAME = BUILDING_NAME
      RENAME_SET_DEFAULT V24 > BUILDING_NUMBER = BUILDING_NUMBER
      RENAME_SET_DEFAULT V25 > SAO_START_NUMBER = SAO_START_NUMBER
      RENAME_SET_DEFAULT V26 > SAO_START_SUFFIX = SAO_START_SUFFIX
      RENAME_SET_DEFAULT V27 > SAO_END_NUMBER = SAO_END_NUMBER
      RENAME_SET_DEFAULT V28 > SAO_END_SUFFIX = SAO_END_SUFFIX
      RENAME_SET_DEFAULT V29 > SAO_TEXT = SAO_TEXT
      RENAME_SET_DEFAULT V30 > ALT_LANGUAGE_SAO_TEXT = ALT_LANGUAGE_SAO_TEXT
      RENAME_SET_DEFAULT V4 > STATE = STATE
      RENAME_SET_DEFAULT V31 > PAO_START_NUMBER = PAO_START_NUMBER
      RENAME_SET_DEFAULT V32 > PAO_START_SUFFIX = PAO_START_SUFFIX
      RENAME_SET_DEFAULT V33 > PAO_END_NUMBER = PAO_END_NUMBER
      RENAME_SET_DEFAULT V34 > PAO_END_SUFFIX = PAO_END_SUFFIX
      RENAME_SET_DEFAULT V35 > PAO_TEXT = PAO_TEXT
      RENAME_SET_DEFAULT V36 > ALT_LANGUAGE_PAO_TEXT = ALT_LANGUAGE_PAO_TEXT
      RENAME_SET_DEFAULT V37 > USRN = USRN
      RENAME_SET_DEFAULT V38 > USRN_MATCH_INDICATOR = USRN_MATCH_INDICATOR
      RENAME_SET_DEFAULT V39 > AREA_NAME = AREA_NAME
      RENAME_SET_DEFAULT V40 > LEVEL = LEVEL
      RENAME_SET_DEFAULT V5 > STATE_DATE = STATE_DATE
      RENAME_SET_DEFAULT V41 > OFFICIAL_FLAG = OFFICIAL_FLAG
      RENAME_SET_DEFAULT V42 > OS_ADDRESS_TOID = OS_ADDRESS_TOID
      RENAME_SET_DEFAULT V43 > OS_ADDRESS_TOID_VERSION = OS_ADDRESS_TOID_VERSION
      RENAME_SET_DEFAULT V44 > OS_ROADLINK_TOID = OS_ROADLINK_TOID
      RENAME_SET_DEFAULT V45 > OS_ROADLINK_TOID_VERSION = OS_ROADLINK_TOID_VERSION
      RENAME_SET_DEFAULT V46 > OS_TOPO_TOID = OS_TOPO_TOID
      RENAME_SET_DEFAULT V47 > OS_TOPO_TOID_VERSION = OS_TOPO_TOID_VERSION
      RENAME_SET_DEFAULT V48 > VOA_CT_RECORD = VOA_CT_RECORD
      RENAME_SET_DEFAULT V49 > VOA_NDR_RECORD = VOA_NDR_RECORD
      RENAME_SET_DEFAULT V50 > STREET_DESCRIPTION = STREET_DESCRIPTION
      RENAME_SET_DEFAULT V6 > CLASS = CLASS
      RENAME_SET_DEFAULT V51 > ALT_LANGUAGE_STREET_DESCRIPTION = ALT_LANGUAGE_STREET_DESCRIPTION
      RENAME_SET_DEFAULT V52 > DEPENDENT_THOROUGHFARE = DEPENDENT_THOROUGHFARE
      RENAME_SET_DEFAULT V53 > THOROUGHFARE = THOROUGHFARE
      RENAME_SET_DEFAULT V54 > WELSH_DEPENDENT_THOROUGHFARE = WELSH_DEPENDENT_THOROUGHFARE
      RENAME_SET_DEFAULT V55 > WELSH_THOROUGHFARE = WELSH_THOROUGHFARE
      RENAME_SET_DEFAULT V56 > DOUBLE_DEPENDENT_LOCALITY = DOUBLE_DEPENDENT_LOCALITY
      RENAME_SET_DEFAULT V57 > DEPENDENT_LOCALITY = DEPENDENT_LOCALITY
      RENAME_SET_DEFAULT V58 > LOCALITY = LOCALITY
      RENAME_SET_DEFAULT V59 > WELSH_DEPENDENT_LOCALITY = WELSH_DEPENDENT_LOCALITY
      RENAME_SET_DEFAULT V60 > WELSH_DOUBLE_DEPENDENT_LOCALITY = WELSH_DOUBLE_DEPENDENT_LOCALITY
      RENAME_SET_DEFAULT V7 > PARENT_UPRN = PARENT_UPRN
      RENAME_SET_DEFAULT V61 > TOWN_NAME = TOWN_NAME
      RENAME_SET_DEFAULT V62 > ADMINISTRATIVE_AREA = ADMINISTRATIVE_AREA
      RENAME_SET_DEFAULT V63 > POST_TOWN = POST_TOWN
      RENAME_SET_DEFAULT V64 > WELSH_POST_TOWN = WELSH_POST_TOWN
      RENAME_SET_DEFAULT V65 > POSTCODE = POSTCODE
      RENAME_SET_DEFAULT V66 > POSTCODE_LOCATOR = POSTCODE_LOCATOR
      RENAME_SET_DEFAULT V67 > POSTCODE_TYPE = POSTCODE_TYPE
      RENAME_SET_DEFAULT V68 > DELIVERY_POINT_SUFFIX = DELIVERY_POINT_SUFFIX
      RENAME_SET_DEFAULT V69 > ADDRESSBASE_POSTAL = ADDRESSBASE_POSTAL
      RENAME_SET_DEFAULT V70 > PO_BOX_NUMBER = PO_BOX_NUMBER
      RENAME_SET_DEFAULT V8 > X_COORDINATE = X_COORDINATE
      RENAME_SET_DEFAULT V71 > WARD_CODE = WARD_CODE
      RENAME_SET_DEFAULT V72 > PARISH_CODE = PARISH_CODE
      RENAME_SET_DEFAULT V73 > RM_START_DATE = RM_START_DATE
      RENAME_SET_DEFAULT V74 > MULTI_OCC_COUNT = MULTI_OCC_COUNT
      RENAME_SET_DEFAULT V75 > VOA_NDR_P_DESC_CODE = VOA_NDR_P_DESC_CODE
      RENAME_SET_DEFAULT V76 > VOA_NDR_SCAT_CODE = VOA_NDR_SCAT_CODE
      RENAME_SET_DEFAULT V77 > ALT_LANGUAGE = ALT_LANGUAGE
      RENAME_SET_DEFAULT V9 > Y_COORDINATE = Y_COORDINATE
      RENAME_SET_DEFAULT V10 > LATITUDE = LATITUDE
    -> AttributeCreator
AttributeCreator
    ATTR_LIST = OBJECTID,@Value(UPRN)
    -> StringPadder
StringPadder
    BLANK_ATTRIBUTE = No
    SRC_ATTRS = UPRN PARENT_UPRN
    WIDTH = 12
    PADCHAR = 0
    SIDE = Left
    -> DateFormatter
DateFormatter
    FMT = FME Date (%Y%m%d)
    SRCFMT = Unknown - Automatic Detection
    DATE_ATTR = STATE_DATE,ENTRY_DATE,LA_START_DATE,LAST_UPDATE_DATE,RM_START_DATE
    INVALID_DATE_VALUE = _FME_NO_OP_
    -> VertexCreator
VertexCreator
    YVAL = @Value(Y_COORDINATE)
    MODE_NAME = Add Point
    XVAL = @Value(X_COORDINATE)
    -> BulkAttributeRenamer
BulkAttributeRenamer
    CASE_CHANGE_TYPE = lower
    ATTRCHOICE = All Attributes
    MODE_CHOICE = RENAME
    PATTERN_ACTION_DISP = CASECHANGE
    -> addressbaseplus_ (writer POSTGIS_1)
    -> FeatureClass1 (writer GEODATABASE_FILE_1)
FeatureClass1 (writer GEODATABASE_FILE_1)
    attributes: uprn integer, udprn char(200), longitude char(200), rpc char(200), local_custodian_code char(200), country char(200), la_start_date char(200), last_update_date char(200), entry_date char(200), rm_organisation_name char(200), la_organisation char(200), department_name char(200), change_type char(200), legal_name char(200), sub_building_name char(200), building_name char(200), building_number char(200), sao_start_number char(200), sao_start_suffix char(200), sao_end_number char(200), sao_end_suffix char(200), sao_text char(200), alt_language_sao_text char(200), state char(200), pao_start_number char(200), pao_start_suffix char(200), pao_end_number char(200), pao_end_suffix char(200), pao_text char(200), alt_language_pao_text char(200),
      usrn char(200), usrn_match_indicator char(200), area_name char(200), level char(200), state_date char(200), official_flag char(200), os_address_toid char(200), os_address_toid_version char(200), os_roadlink_toid char(200), os_roadlink_toid_version char(200), os_topo_toid char(200), os_topo_toid_version char(200), voa_ct_record char(200), voa_ndr_record char(200), street_description char(200), class char(200), alt_language_street_description char(200), dependent_thoroughfare char(200), thoroughfare char(200), welsh_dependent_thoroughfare char(200), welsh_thoroughfare char(200), double_dependent_locality char(200), dependent_locality char(200), locality char(200), welsh_dependent_locality char(200), welsh_double_dependent_locality char(200), parent_uprn char(200), town_name char(200), administrative_area char(200), post_town char(200),
      welsh_post_town char(200), postcode char(200), postcode_locator char(200), postcode_type char(200), delivery_point_suffix char(200), addressbase_postal char(200), po_box_number char(200), x_coordinate char(200), ward_code char(200), parish_code char(200), rm_start_date char(200), multi_occ_count char(200), voa_ndr_p_desc_code char(200), voa_ndr_scat_code char(200), alt_language char(200), y_coordinate char(200), latitude char(200), objectid char(200)
Note: db.dev.london.gov.uk - Postgres 9.1 DEV
addressbaseplus_ (writer POSTGIS_1)
    attributes: uprn serial,PRIKEY, udprn text, change_type text, state text, state_date date, class text, parent_uprn serial,BTREE, x_coordinate float8, y_coordinate float8, latitude float8, longitude float8, rpc text, local_custodian_code text, country text, la_start_date date, last_update_date text, entry_date date, rm_organisation_name text, la_organisation text, department_name text, legal_name text, sub_building_name text, building_name text, building_number text, sao_start_number text, sao_start_suffix text, sao_end_number text, sao_end_suffix text, sao_text text, alt_language_sao_text text,
      pao_start_number text, pao_start_suffix text, pao_end_number text, pao_end_suffix text, pao_text text, alt_language_pao_text text, usrn text, usrn_match_indicator text, area_name text, level text, official_flag text, os_address_toid text, os_address_toid_version text, os_roadlink_toid text, os_roadlink_toid_version text, os_topo_toid text, os_topo_toid_version text, voa_ct_record text, voa_ndr_record text, street_description text, alt_language_street_description text, dependent_thoroughfare text, thoroughfare text, welsh_dependent_thoroughfare text, welsh_thoroughfare text, double_dependent_locality text, dependent_locality text, locality text, welsh_dependent_locality text, welsh_double_dependent_locality text,
      town_name text, administrative_area text, post_town text, welsh_post_town text, postcode text,BTREE, postcode_locator text,BTREE, postcode_type text, delivery_point_suffix text, addressbase_postal text, po_box_number text, ward_code text, parish_code text, rm_start_date text, multi_occ_count text, voa_ndr_p_desc_code text, voa_ndr_scat_code text, alt_language text
