FME workspace esrishape2geodatabase_file.fmw

Parameters:
- DestDataset_GEODATABASE_FILE = C:\temp\osmm_20170804.gdb   # File Geodatabase
- SourceDataset_ESRISHAPE_3 = C:\temp\osmm_20170804\BuildingHeights.shp   # Source Esri Shapefile(s)

Readers:
- ESRISHAPE_2: ESRISHAPE from $(SourceDataset_ESRISHAPE_3)

Writers:
- GEODATABASE_FILE_1: GEODATABASE_FILE to $(DestDataset_GEODATABASE_FILE)

BuildingHeights (reader ESRISHAPE_2)
    attributes: TOID char(80), FtrCd_x long, Vrsn_x long, VrsnDt_x char(80), Thm_x char(80), ThmCnt_x long, ClcltdArVl number(24,15), ChngDt_x char(80), RsnFrChng_ char(80), ChngHstryC char(80), DscrptvGrp char(80), DscrptvG_1 long, DscrptvTrm char(80), DscrptvT_1 long, Mak_x char(80), PhysclLvl_ long, PhysclPrsn char(80), brkn_x char(80), SHAPE_Lngt number(24,15), SHAPE_Ar_x number(24,15), FtrCd_y long, Vrsn_y long, VrsnDt_y char(80), Thm_y char(80), ThmCnt_y long, ClcltdAr_1 number(24,15), ChngDt_y char(80), RsnFrChn_1 char(80), ChngHstr_1 char(80), DscrptvG_2 char(80),
      DscrptvG_3 long, DscrptvT_2 char(80), DscrptvT_3 long, Mak_y char(80), PhysclLv_1 long, PhysclPr_1 char(80), brkn_y char(80), SHAPE_Ln_1 number(24,15), SHAPE_Ar_y number(24,15), OS_TO long, BHA_P char(80), TilRf char(80), AbsHMn number(24,15), AbsH2 number(24,15), AbsHMx number(24,15), RelH2 number(24,15), RlHMx number(24,15), BHA_C long
    -> topoSpatial (writer GEODATABASE_FILE_1)
topoSpatial (writer GEODATABASE_FILE_1)
    attributes: TOID char(80), FtrCd_x integer, Vrsn_x integer, VrsnDt_x char(80), Thm_x char(80), ThmCnt_x integer, ClcltdArVl double(24,15), ChngDt_x char(80), RsnFrChng_ char(80), ChngHstryC char(80), DscrptvGrp char(80), DscrptvG_1 integer, DscrptvTrm char(80), DscrptvT_1 integer, Mak_x char(80), PhysclLvl_ integer, PhysclPrsn char(80), brkn_x char(80), SHAPE_Lngt double(24,15), SHAPE_Ar_x double(24,15), FtrCd_y integer, Vrsn_y integer, VrsnDt_y char(80), Thm_y char(80), ThmCnt_y integer, ClcltdAr_1 double(24,15), ChngDt_y char(80), RsnFrChn_1 char(80), ChngHstr_1 char(80), DscrptvG_2 char(80),
      DscrptvG_3 integer, DscrptvT_2 char(80), DscrptvT_3 integer, Mak_y char(80), PhysclLv_1 integer, PhysclPr_1 char(80), brkn_y char(80), SHAPE_Ln_1 double(24,15), SHAPE_Ar_y double(24,15), OS_TO integer, BHA_P char(80), TilRf char(80), AbsHMn double(24,15), AbsH2 double(24,15), AbsHMx double(24,15), RelH2 double(24,15), RlHMx double(24,15), BHA_C integer
